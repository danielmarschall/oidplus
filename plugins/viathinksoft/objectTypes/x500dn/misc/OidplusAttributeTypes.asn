OidplusAttributeTypes { iso(1) identified-organization(3) dod(6) internet(1) private(4) enterprise(1) 37476 products(2) oidplus(5) v2(2) ds(9) module(1) oidplusAttributeTypes(5) v1(1) }
DEFINITIONS ::=
BEGIN

IMPORTS

  ATTRIBUTE
    FROM InformationFramework
      {joint-iso-itu-t ds(5) module(1) informationFramework(1) 9} WITH SUCCESSORS;


attributeOidplusSystemId ATTRIBUTE ::= {
    WITH SYNTAX   INTEGER
    SINGLE VALUE  TRUE
    LDAP-SYNTAX   directoryString.&id
    LDAP-DESC     "OIDplus System"
    LDAP-NAME     {"OidplusSystemId"}
    ID            id-oidplus-at-sysid
}

attributeOidplusObjectHash ATTRIBUTE ::= {
    WITH SYNTAX   INTEGER
    SINGLE VALUE  TRUE
    LDAP-SYNTAX   directoryString.&id
    LDAP-DESC     "OIDplus Object Hash"
    LDAP-NAME     {"OidplusObjectHash"}
    ID            id-oidplus-at-objhash
}


id-viathinksoft        OBJECT IDENTIFIER ::= { iso(1) identified-organization(3) dod(6) internet(1) private(4) enterprise(1) 37476 }
id-oidplus-v2          OBJECT IDENTIFIER ::= { id-viathinksoft products(2) oidplus(5) v2(2) }
id-oidplus-at-sysid    OBJECT IDENTIFIER ::= { id-oidplus-v2 ds(9) attributeType(4) system-id(1) }
id-oidplus-at-objhash  OBJECT IDENTIFIER ::= { id-oidplus-v2 ds(9) attributeType(4) object-hash(2) }


END
